(setvar "FILEDIA" 0)
(setvar "CMDDIA" 0)
(setq pathFile "C:/Temp/ocsifrovka_work/outpath.txt")
(setq fh (open pathFile "r"))
(if (null fh)
  (progn
    (princ "\nOCIFROVKA_SAVEAS_FAIL missing outpath.txt")
    (command "_.QUIT" "_Y")
  )
  (progn
    (setq outPath (read-line fh))
    (close fh)
    (setq ok nil)
    (foreach fmt '("LT2018" "2018" "LT2013" "2013")
      (if (not ok)
        (progn
          (command "_.SAVEAS" fmt outPath)
          (if (findfile outPath)
            (setq ok T)
          )
        )
      )
    )
    (if ok
      (progn
        (command "_.AUDIT" "_Y")
        (command "_.QSAVE")
        (princ "\nOCIFROVKA_SAVEAS_DONE")
        (princ)
      )
      (progn
        (princ "\nOCIFROVKA_SAVEAS_FAIL")
        (princ)
      )
    )
    (command "_.QUIT" "_Y")
  )
)
(princ)
